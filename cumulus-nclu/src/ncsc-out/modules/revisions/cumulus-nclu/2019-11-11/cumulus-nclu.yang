module cumulus-nclu {
  // Generated by yanger -t ncs
  tailf:mount-id cumulus-nclu-nc-1.0:cumulus-nclu-nc-1.0;
  tailf:ncs-device-type "netconf";

  namespace "http://example.com/cumulus-nclu";
  prefix cumulus;

  import "cumulus-nclu-nc-1.0" {
    prefix "cumulus-nclu-nc-1.0";
  }
  import tailf-ncs {
    prefix ncs;
  }
  import tailf-common {
    prefix tailf;
  }

  revision 2019-11-11 {
    description
      "Initial revision";
  }

  augment "/ncs:devices/ncs:device/ncs:config" {
    container commands {
      tailf:ncs-device-type "netconf";
      tailf:display-when "not(../../ncs:module) or ../../ncs:module[ncs:name='cumulus-nclu']";
      leaf-list cmd {
        ordered-by user;
        type string;
      }
    }
  }
  augment "/ncs:devices/ncs:device/ncs:live-status" {
    container commands {
      tailf:ncs-device-type "netconf";
      tailf:display-when "not(../../ncs:module) or ../../ncs:module[ncs:name='cumulus-nclu'] or (../../ncs:live-status-protocol[not(ncs:capability)]) or (../../ncs:live-status-protocol/ncs:capability/ncs:module[.='cumulus-nclu'])";
      leaf-list cmd {
        ordered-by user;
        type string;
      }
    }
  }
  augment "/ncs:devices/ncs:template/ncs:ned-id/ncs:config" {
    container commands {
      leaf-list cmd {
        // NCS patched for predictable order
        ordered-by user;
        type string;
      }
    }
  }
}
