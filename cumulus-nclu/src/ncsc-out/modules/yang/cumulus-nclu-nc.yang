module cumulus-nclu-nc {
  yang-version 1.1;
  namespace "http://tail-f.com/ns/ned-id/cumulus-nclu-nc";
  prefix cumulus-nclu-nc;

  import tailf-common {
    prefix tailf;
  }

  import tailf-ncs-ned {
    prefix ned;
  }

  identity cumulus-nclu-nc {
    tailf:abstract;
    base ned:netconf-ned-id;
  }
}
