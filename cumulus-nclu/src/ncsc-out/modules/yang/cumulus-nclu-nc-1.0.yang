module cumulus-nclu-nc-1.0 {
  yang-version 1.1;
  namespace "http://tail-f.com/ns/ned-id/cumulus-nclu-nc-1.0";
  prefix cumulus-nclu-nc-1.0;

  import cumulus-nclu-nc {
    prefix family;
  }

  identity cumulus-nclu-nc-1.0 {
    base family:cumulus-nclu-nc;
  }
}
