module ipaddress-allocator-test {
  namespace "http://com/cisco/yang/ipaddressallocatortest";
  prefix ipaddress-allocator-test;

  import ietf-inet-types {
    prefix inet;
  }
  import tailf-common {
    prefix tailf;
  }
  import tailf-ncs {
    prefix ncs;
  }

  augment /ncs:services {

    list ipaddress-allocator-test {
      key name;
      description "This is a test service for ipaddress-allocator";

      ncs:servicepoint ipaddress-allocator-test-servicepoint;

      leaf name {
        tailf:info "Unique service id";
        tailf:cli-allow-range;
        type string;
      }

      leaf subnet-size {
        tailf:info "Prefix length of subnet to be allocated";
        type uint8;
      }

      leaf redeploy-option {
        tailf:info "(optional) Redeploy option to be used by the service for the allocation request.";
        type enumeration {
          enum "default";
          enum "touch";
          enum "reactive-re-deploy";
          enum "re-deploy";
        }
      }

      leaf allocated {
        type empty;
        config false;
      }

      leaf deploys {
        type uint32;
        config false;
      }

      uses ncs:service-data;
    }

    list ipa-static-test {
      key name;
      description "This is a test service for the static ipaddress-allocator";

      ncs:servicepoint ipa-static-test-servicepoint;

      leaf name {
        tailf:info "Unique service id";
        tailf:cli-allow-range;
        type string;
      }

      leaf subnet-size {
        tailf:info "Prefix length of subnet to be allocated";
        type uint8;
      }

      leaf subnet-start-ip {
        type inet:ip-address;
      }

      leaf allocated {
        type empty;
        config false;
      }

      leaf deploys {
        type uint32;
        config false;
      }

      uses ncs:service-data;
    }

  list ipa-fail-realloc-test {
      key name;
      description "This is a test service for the static ipaddress-allocator";

      ncs:servicepoint ipa-fail-realloc-test-servicepoint;

      leaf name {
        tailf:info "Unique service id";
        tailf:cli-allow-range;
        type string;
      }

      leaf subnet-size {
        tailf:info "Prefix length of subnet to be allocated";
        type uint8;
      }

      leaf allocated {
        type empty;
        config false;
      }

      leaf deploys {
        type uint32;
        config false;
      }

      uses ncs:service-data;
    }
  }

}
